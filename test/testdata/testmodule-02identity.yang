module testmodule-02identity {
  namespace "urn:ns-02identity";
  prefix pre-01;

  identity id-01;

  identity id-02 {  }
  
  identity id-03 {
    base id-01;
  }

  identity id-04 {
    status current;
  }

  identity id-05 {
    description "desc-01";
  }

  identity id-06 {
    reference "ref-01";
  }
}
