module testmodule-00comment {

  namespace "urn:ns-00comment";
  prefix pre-01;

  // container ignored-container {
  // }
  /* container ignored-container2 {
  
  } */

  organization "This string contains /* and */.";
  description "// This string starts and ends with //.";
}
