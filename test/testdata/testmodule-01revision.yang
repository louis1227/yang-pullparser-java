module testmodule-01revision {
  namespace "urn:ns-01revision";
  prefix pre-01;

  revision 2010-04-21;
 
    revision 2009-03-07 {
    description "desc-01";
  }

  revision 2008-02-15 {

      reference "ref-01";
    }

  revision 2007-01-01 {
    reference "ref-02";
    description "desc-02";
  }
}
