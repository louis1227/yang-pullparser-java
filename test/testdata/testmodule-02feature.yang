module testmodule-02feature {
  namespace "urn:ns-02feature";
  prefix pre-01;

  feature feat-01  ;

  feature feat-02 {
    if-feature feat-04 ;
  }

  feature feat-03 {
    if-feature feat-01 ;
    if-feature feat-02 ;
  }

  feature feat-04 { 
    status obsolete;
  }

  feature feat-05 {
    description "desc-01";
  }

  feature feat-06 {
    reference "ref-01";
  }
}
