module testmodule-01linkage {
  namespace "urn:ns-01linkage";
  prefix pre-01;

  include submodule-01;

  include submodule-02 {
    revision-date 2019-01-03;
  }

  import testmodule-01revision {
    prefix em01;
    revision-date 2008-02-15;
  }
}
